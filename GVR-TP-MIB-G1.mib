GVR-TP-MIB-G1 DEFINITIONS ::= BEGIN

IMPORTS
	MODULE-IDENTITY,
	OBJECT-TYPE,
	Gauge32,
	Integer32
		FROM SNMPv2-SMI
	TEXTUAL-CONVENTION
		FROM SNMPv2-TC
	OBJECT-GROUP
		FROM SNMPv2-CONF;

gvrtpg1MIB MODULE-IDENTITY
	LAST-UPDATED "202510292218Z"	-- 2025-10-29 22:18:00
	ORGANIZATION "Universidade do Minho Meti GVR G1"
	CONTACT-INFO
		"Alunos do grupo 1 de GVR Meti

		Diogo Araújo
		Bruno Magalhães
		Junlin Lu"
	DESCRIPTION
		"Versão inicial da MIB para o projeto de Gestão de Redes"
	REVISION "202510292218Z"	-- 2025-10-29 22:18:00
	DESCRIPTION
		"Initial version."
	-- 1.3.6.1.3.2025
	::= { 1  3  6  1  3  2025 }


LaneID ::= TEXTUAL-CONVENTION
	DISPLAY-HINT "d"
	STATUS  current
	DESCRIPTION
		"Identificador unívoco para uma via (lane) no sistema de simulação."
	SYNTAX Integer32 (1..2147483647)


SemaphoreColor ::= TEXTUAL-CONVENTION
	STATUS  current
	DESCRIPTION
		"A cor atual do semáforo."
	SYNTAX INTEGER {
			green(1),
			yellow(2),
			red(3) }


-- Scalars and Tables
--

gvrtpg1Objects OBJECT IDENTIFIER 
	-- 1.3.6.1.3.2025.1
	::= { gvrtpg1MIB 1 }

laneTable OBJECT-TYPE
	SYNTAX  SEQUENCE OF LaneEntry
	MAX-ACCESS not-accessible
	STATUS  current
	DESCRIPTION
		"Tabela de todas as vias rodoviárias com dados relevantes às mesmas"
	-- 1.3.6.1.3.2025.1.1
	::= { gvrtpg1Objects 1 }


laneEntry OBJECT-TYPE
	SYNTAX  LaneEntry
	MAX-ACCESS not-accessible
	STATUS  current
	DESCRIPTION
		"Uma linha de uma via."
	INDEX {
		laneID }
	-- 1.3.6.1.3.2025.1.1.1
	::= { laneTable 1 }


LaneEntry ::= SEQUENCE {

	laneID         LaneID,
	vehicleCount   Gauge32,
	semaphoreColor SemaphoreColor,
	timeToChange   Integer32,
	capacity       Integer32,
	rgt            Integer32,
	totalVeh       Integer32,
	viaterminal    INTEGER }


laneID OBJECT-TYPE
	SYNTAX  LaneID (1..60)
	MAX-ACCESS not-accessible
	STATUS  current
	DESCRIPTION
		"Identificação unívoca da via (índice da tabela)"
	-- 1.3.6.1.3.2025.1.1.1.1
	::= { laneEntry 1 }


vehicleCount OBJECT-TYPE
	SYNTAX  Gauge32
	UNITS	"vehicles"
	MAX-ACCESS read-only
	STATUS  current
	DESCRIPTION
		"Número de veículos que estão atualmente na via."
	-- 1.3.6.1.3.2025.1.1.1.2
	::= { laneEntry 2 }


semaphoreColor OBJECT-TYPE
	SYNTAX  SemaphoreColor
	MAX-ACCESS read-only
	STATUS  current
	DESCRIPTION
		"A cor atual do semáforo no final da via "
	-- 1.3.6.1.3.2025.1.1.1.3
	::= { laneEntry 3 }


timeToChange OBJECT-TYPE
	SYNTAX  Integer32 (0..2147483647)
	UNITS	"seconds"
	MAX-ACCESS read-only
	STATUS  current
	DESCRIPTION
		"O tempo que falta para o semáforo mudar de cor"
	-- 1.3.6.1.3.2025.1.1.1.4
	::= { laneEntry 4 }


capacity OBJECT-TYPE
	SYNTAX  Integer32
	UNITS	"veiculos"
	MAX-ACCESS read-only
	STATUS  current
	DESCRIPTION
		"Capacidade máxima de veiculos na via"
	-- 1.3.6.1.3.2025.1.1.1.5
	::= { laneEntry 5 }


rgt OBJECT-TYPE
	SYNTAX  Integer32
	UNITS	"Veiculos/seg"
	MAX-ACCESS read-only
	STATUS  current
	DESCRIPTION
		"Fluxo da via, velocidade em que os veiculos se movem na mesma"
	-- 1.3.6.1.3.2025.1.1.1.6
	::= { laneEntry 6 }


totalVeh OBJECT-TYPE
	SYNTAX  Integer32
	UNITS	"Veiculos"
	MAX-ACCESS read-only
	STATUS  current
	DESCRIPTION
		"Número total de veiculos que percorreu esta via"
	-- 1.3.6.1.3.2025.1.1.1.7
	::= { laneEntry 7 }


viaterminal OBJECT-TYPE
	SYNTAX  INTEGER {
			truth(1),
			false(2) }
	MAX-ACCESS read-only
	STATUS  current
	DESCRIPTION
		"Indica se a via é terminal (truth-1 false-2)"
	-- 1.3.6.1.3.2025.1.1.1.8
	::= { laneEntry 8 }


viaDestTable OBJECT-TYPE
	SYNTAX  SEQUENCE OF ViaDestEntry
	MAX-ACCESS not-accessible
	STATUS  current
	DESCRIPTION
		"Tabela com chave estrangeira da laneTable onde 
		tem colunas relevantes sobre as vias destino"
	-- 1.3.6.1.3.2025.1.2
	::= { gvrtpg1Objects 2 }


viaDestEntry OBJECT-TYPE
	SYNTAX  ViaDestEntry
	MAX-ACCESS not-accessible
	STATUS  current
	DESCRIPTION
		"Linha com possivel destino"
	INDEX {
		id,
		laneID }
	-- 1.3.6.1.3.2025.1.2.1
	::= { viaDestTable 1 }


ViaDestEntry ::= SEQUENCE {

	id        Integer32,
	destVia   Integer32,
	fluxoDest Integer32 }


id OBJECT-TYPE
	SYNTAX  Integer32 (1..2147483647)
	MAX-ACCESS not-accessible
	STATUS  current
	DESCRIPTION
		"id unico para cada linha"
	-- 1.3.6.1.3.2025.1.2.1.1
	::= { viaDestEntry 1 }


destVia OBJECT-TYPE
	SYNTAX  Integer32 (1..2147483647)
	MAX-ACCESS read-only
	STATUS  current
	DESCRIPTION
		"via de destino possivel para uma laneID"
	-- 1.3.6.1.3.2025.1.2.1.2
	::= { viaDestEntry 2 }


fluxoDest OBJECT-TYPE
	SYNTAX  Integer32 (1..2147483647)
	UNITS	"veiculos/segundo"
	MAX-ACCESS read-only
	STATUS  current
	DESCRIPTION
		"Fluxo da via de destino"
	-- 1.3.6.1.3.2025.1.2.1.3
	::= { viaDestEntry 3 }


-- Notification Types
--

gvrtpg1Events OBJECT IDENTIFIER 
	-- 1.3.6.1.3.2025.2
	::= { gvrtpg1MIB 2 }

-- Conformance
--

gvrtpg1Conf OBJECT IDENTIFIER 
	-- 1.3.6.1.3.2025.3
	::= { gvrtpg1MIB 3 }

-- Groups
--

gvrtpg1Groups OBJECT IDENTIFIER 
	-- 1.3.6.1.3.2025.3.1
	::= { gvrtpg1Conf 1 }

-- Compliances
--

gvrtpg1Compliances OBJECT IDENTIFIER 
	-- 1.3.6.1.3.2025.3.2
	::= { gvrtpg1Conf 2 }

gvrtpg1BasicGroup OBJECT-GROUP
	OBJECTS {
		vehicleCount,
		semaphoreColor,
		timeToChange,
		capacity,
		rgt,
		totalVeh,
		viaterminal,
		destVia,
		fluxoDest }
	STATUS  current
	DESCRIPTION
		"Basic objects."
	-- 1.3.6.1.3.2025.3.1.1
	::= { gvrtpg1Groups 1 }

END
